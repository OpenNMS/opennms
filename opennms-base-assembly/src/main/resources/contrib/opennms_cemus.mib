--
-- OPENNMS-SNMPv2-MIB       module definition
--
-- Copyright (C) 2011 by The OpenNMS Group, Inc.
-- Version 1.0.0 - 2011-03-14: Migrated OpenNMS default Trap to SMI 2
-- Version 1.0.1 - 2011-03-28: Added Objects openNMS-eventsAlarms OpenNMS-AlarmId and openNMS-synchronizing to 
--                             host information regarding alarms and synchronization
-- Version 1.0.2 - 2011-03-31: Added OpenNMS-alarmTrap, openNMS-heartbeatTrap
--                             openNMS-startSyncTrap, openNMS-endSyncTrap, openNMS-syncRequestTrap
--


OPENNMS-SNMPv2-MIB DEFINITIONS ::= BEGIN
IMPORTS
   MODULE-IDENTITY, OBJECT-TYPE, NOTIFICATION-TYPE, IpAddress, TimeTicks, enterprises FROM SNMPv2-SMI
   DisplayString FROM SNMPv2-TC
   MODULE-COMPLIANCE, OBJECT-GROUP,
   NOTIFICATION-GROUP                  FROM SNMPv2-CONF;

   openNMS      MODULE-IDENTITY
                LAST-UPDATED "201104020000Z"    -- Apr. 2, 2011
                ORGANIZATION "The OpenNMS Group, Inc.,"
                CONTACT-INFO "The OpenNMS Group, Inc.
 			      220 Chatham Business Drive
                              Pittsboro, NC 27312
                              United States
                              Phone: +1 919-533-0160
                              WEB: www.opennms.org"
                DESCRIPTION
                "The MIB module High Availability MIB.
                Copyright (c) 2002-2003 Brocade Communications Systems, Inc.
                                All rights reserved."
		       
                REVISION    "201104020000Z"
		DESCRIPTION "Initial version."
	::= { enterprises 5813 }

openNMS-traps	OBJECT IDENTIFIER
	::= { openNMS 3 }

openNMS-Groups 	OBJECT IDENTIFIER
	::= { openNMS 4 }

openNMS-data	OBJECT IDENTIFIER
	::= { openNMS 20 }

openNMS-events	OBJECT IDENTIFIER
	::= { openNMS-data 1 }

openNMS-eventsSpecific	OBJECT IDENTIFIER
	::= { openNMS-data 2 }    
							
openNMS-eventsAlarms	OBJECT IDENTIFIER
	::= { openNMS-data 3 }														
							
tl1AutonomousMessage	OBJECT IDENTIFIER
	::= { openNMS-eventsSpecific 1 }

openNMS-event-dbid		OBJECT-TYPE
	SYNTAX		DisplayString
	MAX-ACCESS		read-only
	STATUS		current
	DESCRIPTION 	"This is the database ID for the event. Each
			event in OpenNMS is assigned a unique, sequential
			eventid. Unless the database is cleared, the 
			sequence should never repeat."
	::= { openNMS-events 1 }

openNMS-event-distPoller	OBJECT-TYPE
	SYNTAX		DisplayString
	MAX-ACCESS		read-only
	STATUS		current
	DESCRIPTION 	"This is the distributed poller name for the event."
	::= { openNMS-events 2 }

openNMS-event-create-time	OBJECT-TYPE
	SYNTAX		DisplayString
	MAX-ACCESS		read-only
	STATUS		current
	DESCRIPTION 	"This is the time the event was created in the database."
	::= { openNMS-events 3 }

openNMS-event-master-station	OBJECT-TYPE
	SYNTAX		DisplayString
	MAX-ACCESS		read-only
	STATUS		current
	DESCRIPTION 	"This is the name of the master station for the event."
	::= { openNMS-events 4 }

openNMS-event-uei		OBJECT-TYPE
	SYNTAX		DisplayString
	MAX-ACCESS		read-only
	STATUS		current
	DESCRIPTION 	"This is the Unique Event Identifier (UEI) for the event.
			 The UEI is a string that should be descriptive and unique
			 for each event type that OpenNMS handles."
	::= { openNMS-events 6 }

openNMS-event-source		OBJECT-TYPE
	SYNTAX		DisplayString
	MAX-ACCESS		read-only
	STATUS		current
	DESCRIPTION 	"This is the source of the event, usually the OpenNMS process
			name, such as Capsd or Trapd."
	::= { openNMS-events 7 }

openNMS-event-nodeid		OBJECT-TYPE
	SYNTAX		DisplayString
	MAX-ACCESS		read-only
	STATUS		current
	DESCRIPTION 	"This is the Node ID for the event. Node IDs are simply
			a handle that OpenNMS uses to group interfaces and services
			together, and each node should represent an actual device."
	::= { openNMS-events 8 }

openNMS-event-time		OBJECT-TYPE
	SYNTAX		DisplayString
	MAX-ACCESS		read-only
	STATUS		current
	DESCRIPTION 	"This is the time the event occurred."
	::= { openNMS-events 9 }

openNMS-event-host		OBJECT-TYPE
	SYNTAX		DisplayString
	MAX-ACCESS		read-only
	STATUS		current
	DESCRIPTION 	"This is the host for the event. In most cases it will
			represent the OpenNMS instance that generated it."
	::= { openNMS-events 10 }

openNMS-event-interface		OBJECT-TYPE
	SYNTAX		DisplayString
	MAX-ACCESS		read-only
	STATUS		current
	DESCRIPTION 	"This is the interface for the event. It should contain
			the IP address of the interface that caused the event."
	::= { openNMS-events 11 }

openNMS-event-snmphost		OBJECT-TYPE
	SYNTAX		DisplayString
	MAX-ACCESS		read-only
	STATUS		current
	DESCRIPTION 	"This is the SNMP host for the event. In the case of
			an SNMP Trap that was received by OpenNMS, it will 
			reflect the device that generated the trap. In the
			case of a trap generated by OpenNMS, such as forwarding
			a nodeLostService event to another system, it will
			reflect the OpenNMS server."
	::= { openNMS-events 12 }

openNMS-event-service		OBJECT-TYPE
	SYNTAX		DisplayString
	MAX-ACCESS		read-only
	STATUS		current
	DESCRIPTION 	"This is the name of the service (ICMP, SSH, HTTP, etc.)
			that is associated with the event. For example, a failed 
			web server may generate a nodeLostService event. In that
			case this field would most likely read HTTP."
	::= { openNMS-events 13 }

openNMS-event-descr		OBJECT-TYPE
	SYNTAX		DisplayString
	MAX-ACCESS		read-only
	STATUS		current
	DESCRIPTION 	"This is the verbose description of the event."
	::= { openNMS-events 16 }

openNMS-event-logmsg		OBJECT-TYPE
	SYNTAX		DisplayString
	MAX-ACCESS		read-only
	STATUS		current
	DESCRIPTION 	"The log message is a short, usually one sentence, description of
			the event suitable for displaying in a log or table."
	::= { openNMS-events 17 }

openNMS-event-severity		OBJECT-TYPE
	SYNTAX		DisplayString
	MAX-ACCESS		read-only
	STATUS		current
	DESCRIPTION 	"This is the severity of the event, one of CLEARED,
			INDETERMINATE, NORMAL, WARNING, MINOR, MAJOR or CRITICAL."
	::= { openNMS-events 18 }

openNMS-event-pathoutage	OBJECT-TYPE
	SYNTAX		DisplayString
	MAX-ACCESS		read-only
	STATUS		current
	DESCRIPTION 	"The pathoutage field in the event has yet to be implemented,
			but it will be stored here when available."
	::= { openNMS-events 19 }

openNMS-event-operinst		OBJECT-TYPE
	SYNTAX		DisplayString
	MAX-ACCESS		read-only
	STATUS		current
	DESCRIPTION 	"It is possible to associate operator instructions with
			events in OpenNMS. If this information is available, it 
			will be stored here."
	::= { openNMS-events 20 }

openNMS-event-ifresolve		OBJECT-TYPE
	SYNTAX		DisplayString
	MAX-ACCESS		read-only
	STATUS		current
	DESCRIPTION 	"An attempt will be made to resolve the FQDN of
			the IP address in OpenNMS-event-interface and
			if successful, the value returned will be stored here."
	::= { openNMS-events 21 }

openNMS-event-nodelabel		OBJECT-TYPE
	SYNTAX		DisplayString
	MAX-ACCESS		read-only
	STATUS		current
	DESCRIPTION 	"This will contain the name of the node as known by OpenNMS. 
			This is based solely on OpenNMS-event-nodeid and can be
			considered an authoritative way to identify the device from
			the perspective of OpenNMS.

			This name is automatically assigned in the following order:

			1) DNS Name: The reverse-resolved name of the primary
			interface for the node.

			2) NetBIOS Name: If available on a Windows or SMB system.

			3) SNMP sysName: If SNMP is available, the sysName.

			4) IP Address

			All of these methods can be overridden by an end user via the webUI, 
			and thus the value can change over time, although the 
			OpenNMS-event-nodeid will not."
	::= { openNMS-events 22 }

tl1amRawMessage	OBJECT-TYPE
	SYNTAX		DisplayString
	MAX-ACCESS		read-only
	STATUS		current
	DESCRIPTION
				"The raw TL1 autonomous message in its entirety."
	::= { tl1AutonomousMessage 1 }
	
tl1amAlarmCode	OBJECT-TYPE
	SYNTAX		DisplayString
	MAX-ACCESS		read-only
	STATUS		current
	DESCRIPTION
				"The ASCII alarm-code for this TL1 autonomous message."
	::= { tl1AutonomousMessage 2 }

tl1amAutonomousTag	OBJECT-TYPE
	SYNTAX			DisplayString
	MAX-ACCESS			read-only
	STATUS			current
	DESCRIPTION
				"The ASCII autonomous-tag for this TL1 autonomous message."
	::= { tl1AutonomousMessage 3 }

tl1amVerb		OBJECT-TYPE
	SYNTAX		DisplayString
	MAX-ACCESS		read-only
	STATUS		current
	DESCRIPTION
				"The ASCII verb for this TL1 autonomous message.
				Should always be REPT."
	::= { tl1AutonomousMessage 4 }

tl1amAutoBlock	OBJECT-TYPE
	SYNTAX		DisplayString
	MAX-ACCESS		read-only
	STATUS		current
	DESCRIPTION
				"The ASCII auto-block for this TL1 autonomous message."
	::= { tl1AutonomousMessage 5 }

tl1amAID		OBJECT-TYPE
	SYNTAX		DisplayString
	MAX-ACCESS		read-only
	STATUS		current
	DESCRIPTION
				"The ASCII AID (MAX-ACCESS identifier) for this TL1 autonomous
				message, as parsed from the auto-block."
	::= { tl1AutonomousMessage 6 }

tl1amAdditionalParams	OBJECT-TYPE
	SYNTAX				DisplayString
	MAX-ACCESS				read-only
	STATUS				current
	DESCRIPTION
						"The additional parameters for this TL1 autonomous message,
						as parsed from the auto-block."
	::= { tl1AutonomousMessage 7 }
				   
openNMS-alarmId		OBJECT-TYPE
	SYNTAX		DisplayString
	MAX-ACCESS		read-only
	STATUS		current
	DESCRIPTION 	"The unique alarm identifier."
	::= { openNMS-eventsAlarms 1 } 
 
openNMS-synchronizing		OBJECT-TYPE
	SYNTAX		DisplayString
	MAX-ACCESS		read-only
	STATUS		current
	DESCRIPTION 	"flag indicating if the alarm is due to 
                         a synchronization session (SYNC) or not (NORMAL)"
	::= { openNMS-eventsAlarms 2 }
					   							   
openNMS-Generic-Trap	NOTIFICATION-TYPE
	OBJECTS {
		openNMS-event-dbid,
		openNMS-event-distPoller,
		openNMS-event-create-time,
		openNMS-event-master-station,
		openNMS-event-uei,
		openNMS-event-source,
		openNMS-event-nodeid,
		openNMS-event-time,
		openNMS-event-host,
		openNMS-event-interface,
		openNMS-event-snmphost,
		openNMS-event-service,
		openNMS-event-descr,
		openNMS-event-logmsg,
		openNMS-event-severity,
		openNMS-event-pathoutage,
		openNMS-event-operinst,
		openNMS-event-ifresolve,
		openNMS-event-nodelabel
		}
	STATUS	current
	DESCRIPTION 
	"This is the definition of the generic OpenNMS trap sent from the
	scriptd process. Key variables are uei (which tells what type
	of OpenNMS event this was), interface (the IP address of the interface
	that caused the event) and severity."
	::=  {  openNMS-traps  1  }

openNMS-tl1AutonomousMessageTrap	NOTIFICATION-TYPE	
	OBJECTS {
		openNMS-event-nodeid,
		openNMS-event-time,
		openNMS-event-host,
		openNMS-event-interface,
		openNMS-event-service,
		openNMS-event-severity,
		tl1amRawMessage,
		tl1amAlarmCode,
		tl1amAutonomousTag,
		tl1amVerb,
		tl1amAutoBlock,
		tl1amAID,
		tl1amAdditionalParams
	}
	STATUS			current
	DESCRIPTION
		"This trap is used to convey the contents of a TL1 autonomous message
		received from a TL1 NE or a north-bound TL1 EMS. Managers receiving
		this trap may need to perform additional analysis of its varbinds in
		order to realize value from this trap."
	::=  {  openNMS-traps  2  }

openNMS-alarmTrap	NOTIFICATION-TYPE
	OBJECTS		{ 		
		openNMS-event-dbid,
		openNMS-event-distPoller,
		openNMS-event-create-time,
		openNMS-event-master-station,
		openNMS-event-uei,
		openNMS-event-source,
		openNMS-event-nodeid,
		openNMS-event-time,
		openNMS-event-host,
		openNMS-event-interface,
		openNMS-event-snmphost,
		openNMS-event-service,
		openNMS-event-descr,
		openNMS-event-logmsg,
		openNMS-event-severity,
		openNMS-event-pathoutage,
		openNMS-event-operinst,
		openNMS-event-ifresolve,
		openNMS-event-nodelabel,
		openNMS-alarmId,
		openNMS-synchronizing 
		}
	STATUS			current
	DESCRIPTION		
		"The OpenNMS alarm SNMP Trap"
		
	::=  {  openNMS-traps 3  }

openNMS-heartbeatTrap	NOTIFICATION-TYPE   
	STATUS			current
	DESCRIPTION
		"Trap sent periodically by OpenNMS to keep alive external SNMP Manager"
	::=  {  openNMS-traps  4  }
             
openNMS-startSyncTrap	NOTIFICATION-TYPE      
	STATUS			current
	DESCRIPTION
		"OpenNMS Synchronization Process is starting"
	::=  {  openNMS-traps  5  }
                                           
openNMS-endSyncTrap	NOTIFICATION-TYPE      
	STATUS			current
	DESCRIPTION
		"OpenNMS Synchronization Process is successfully ended"
	::=  {  openNMS-traps  6  }
                                           
openNMS-syncRequestTrap NOTIFICATION-TYPE  
	STATUS			current
  	DESCRIPTION 
    	"OpenNMS synchronization request" 
	::=  {  openNMS-traps  7  }       

openNMS-events-Group	OBJECT-GROUP
	OBJECTS {
		openNMS-event-dbid,
		openNMS-event-distPoller,
		openNMS-event-create-time,
		openNMS-event-master-station,
		openNMS-event-uei,
		openNMS-event-source,
		openNMS-event-nodeid,
		openNMS-event-time,
		openNMS-event-host,
		openNMS-event-interface,
		openNMS-event-snmphost,
		openNMS-event-service,
		openNMS-event-descr,
		openNMS-event-logmsg,
		openNMS-event-severity,
		openNMS-event-pathoutage,
		openNMS-event-operinst,
		openNMS-event-ifresolve,
		openNMS-event-nodelabel
	}
	STATUS current
	DESCRIPTION 
		"Conformance Group for OpenNMS Events"
	::= { openNMS-Groups 1 }
							
tl1AutonomousMessage-Group	OBJECT-GROUP
	OBJECTS {
		tl1amRawMessage,
		tl1amAlarmCode,
		tl1amAutonomousTag,
		tl1amVerb,
		tl1amAutoBlock,
		tl1amAID,
		tl1amAdditionalParams
	}
	STATUS current
	DESCRIPTION 
		"Conformance Group for TL1 autonomous message"
	::= { openNMS-Groups 2 }

openNMS-eventsAlarms-Group	OBJECT-GROUP
	OBJECTS {
		openNMS-alarmId,
		openNMS-synchronizing
	}
	STATUS current
	DESCRIPTION 
		"Conformance Group for OpenNMS Events related to Alarms "
	::= { openNMS-Groups 3 }																	

openNMS-traps-Group	NOTIFICATION-GROUP
	NOTIFICATIONS {
		openNMS-Generic-Trap,
		openNMS-tl1AutonomousMessageTrap,
		openNMS-alarmTrap, 
		openNMS-heartbeatTrap,
                openNMS-startSyncTrap, 
		openNMS-endSyncTrap, 
		openNMS-syncRequestTrap
	}
	STATUS current
	DESCRIPTION 
		"OpenNMS Notification Group"
	::= { openNMS-Groups 4 }	

END
