--
-- OPENNMS-SNMPv2-MIB       module definition
--
-- Copyright (C) 2011 by The OpenNMS Group, Inc.
-- Version 1.0.0 - 2011-03-14: Migrated OpenNMS default Trap to SMI 2
-- Version 1.0.1 - 2011-03-28: Added Objects openNMS-eventsAlarms OpenNMS-AlarmId and openNMS-synchronizing to 
--                             host information regarding alarms and synchronization
-- Version 1.0.2 - 2011-03-31: Added OpenNMS-alarmTrap, openNMS-heartbeatTrap
--                             openNMS-startSyncTrap, openNMS-endSyncTrap, openNMS-syncRequestTrap
-- Version 1.0.3 - 2011-04-02: Removed all the OpenNMS prefixes
--


OPENNMS-SNMPv2-MIB DEFINITIONS ::= BEGIN
IMPORTS
   MODULE-IDENTITY, OBJECT-TYPE, NOTIFICATION-TYPE, enterprises FROM SNMPv2-SMI
   DisplayString FROM SNMPv2-TC
   MODULE-COMPLIANCE, OBJECT-GROUP,
   NOTIFICATION-GROUP                  FROM SNMPv2-CONF;

   openNMS      MODULE-IDENTITY
                LAST-UPDATED "201104020000Z"    -- Apr. 2, 2011
                ORGANIZATION "The OpenNMS Group, Inc.,"
                CONTACT-INFO "The OpenNMS Group, Inc.
 			      220 Chatham Business Drive
                              Pittsboro, NC 27312
                              United States
                              Phone: +1 919-533-0160
                              WEB: www.opennms.org"
                DESCRIPTION
                "The MIB module High Availability MIB.
                Copyright (c) 2002-2003 Brocade Communications Systems, Inc.
                                All rights reserved."
		       
                REVISION    "201104020000Z"
		DESCRIPTION "Initial version."
	::= { enterprises 5813 }

traps	OBJECT IDENTIFIER
	::= { openNMS 1 }

groups 	OBJECT IDENTIFIER
	::= { openNMS 4 }

data	OBJECT IDENTIFIER
	::= { openNMS 20 }

events	OBJECT IDENTIFIER
	::= { data 1 }

eventsSpecific	OBJECT IDENTIFIER
	::= { data 2 }    
							
eventsAlarms	OBJECT IDENTIFIER
	::= { data 3 }														
							
tl1AutonomousMessage	OBJECT IDENTIFIER
	::= { eventsSpecific 1 }

dbid		OBJECT-TYPE
	SYNTAX		DisplayString
	MAX-ACCESS		read-only
	STATUS		current
	DESCRIPTION 	"This is the database ID for the event. Each
			event in OpenNMS is assigned a unique, sequential
			eventid. Unless the database is cleared, the 
			sequence should never repeat."
	::= { events 1 }

distPoller	OBJECT-TYPE
	SYNTAX		DisplayString
	MAX-ACCESS		read-only
	STATUS		current
	DESCRIPTION 	"This is the distributed poller name for the event."
	::= { events 2 }

create-time	OBJECT-TYPE
	SYNTAX		DisplayString
	MAX-ACCESS		read-only
	STATUS		current
	DESCRIPTION 	"This is the time the event was created in the database."
	::= { events 3 }

master-station	OBJECT-TYPE
	SYNTAX		DisplayString
	MAX-ACCESS		read-only
	STATUS		current
	DESCRIPTION 	"This is the name of the master station for the event."
	::= { events 4 }

uei		OBJECT-TYPE
	SYNTAX		DisplayString
	MAX-ACCESS		read-only
	STATUS		current
	DESCRIPTION 	"This is the Unique Event Identifier (UEI) for the event.
			 The UEI is a string that should be descriptive and unique
			 for each event type that OpenNMS handles."
	::= { events 6 }

source		OBJECT-TYPE
	SYNTAX		DisplayString
	MAX-ACCESS		read-only
	STATUS		current
	DESCRIPTION 	"This is the source of the event, usually the OpenNMS process
			name, such as Capsd or Trapd."
	::= { events 7 }

nodeid		OBJECT-TYPE
	SYNTAX		DisplayString
	MAX-ACCESS		read-only
	STATUS		current
	DESCRIPTION 	"This is the Node ID for the event. Node IDs are simply
			a handle that OpenNMS uses to group interfaces and services
			together, and each node should represent an actual device."
	::= { events 8 }

time		OBJECT-TYPE
	SYNTAX		DisplayString
	MAX-ACCESS		read-only
	STATUS		current
	DESCRIPTION 	"This is the time the event occurred."
	::= { events 9 }

host		OBJECT-TYPE
	SYNTAX		DisplayString
	MAX-ACCESS		read-only
	STATUS		current
	DESCRIPTION 	"This is the host for the event. In most cases it will
			represent the OpenNMS instance that generated it."
	::= { events 10 }

interface		OBJECT-TYPE
	SYNTAX		DisplayString
	MAX-ACCESS		read-only
	STATUS		current
	DESCRIPTION 	"This is the interface for the event. It should contain
			the IP address of the interface that caused the event."
	::= { events 11 }

snmphost		OBJECT-TYPE
	SYNTAX		DisplayString
	MAX-ACCESS		read-only
	STATUS		current
	DESCRIPTION 	"This is the SNMP host for the event. In the case of
			an SNMP Trap that was received by OpenNMS, it will 
			reflect the device that generated the trap. In the
			case of a trap generated by OpenNMS, such as forwarding
			a nodeLostService event to another system, it will
			reflect the OpenNMS server."
	::= { events 12 }

service		OBJECT-TYPE
	SYNTAX		DisplayString
	MAX-ACCESS		read-only
	STATUS		current
	DESCRIPTION 	"This is the name of the service (ICMP, SSH, HTTP, etc.)
			that is associated with the event. For example, a failed 
			web server may generate a nodeLostService event. In that
			case this field would most likely read HTTP."
	::= { events 13 }

descr		OBJECT-TYPE
	SYNTAX		DisplayString
	MAX-ACCESS		read-only
	STATUS		current
	DESCRIPTION 	"This is the verbose description of the event."
	::= { events 16 }

logmsg		OBJECT-TYPE
	SYNTAX		DisplayString
	MAX-ACCESS		read-only
	STATUS		current
	DESCRIPTION 	"The log message is a short, usually one sentence, description of
			the event suitable for displaying in a log or table."
	::= { events 17 }

severity		OBJECT-TYPE
	SYNTAX		DisplayString
	MAX-ACCESS		read-only
	STATUS		current
	DESCRIPTION 	"This is the severity of the event, one of CLEARED,
			INDETERMINATE, NORMAL, WARNING, MINOR, MAJOR or CRITICAL."
	::= { events 18 }

pathoutage	OBJECT-TYPE
	SYNTAX		DisplayString
	MAX-ACCESS		read-only
	STATUS		current
	DESCRIPTION 	"The pathoutage field in the event has yet to be implemented,
			but it will be stored here when available."
	::= { events 19 }

operinst		OBJECT-TYPE
	SYNTAX		DisplayString
	MAX-ACCESS		read-only
	STATUS		current
	DESCRIPTION 	"It is possible to associate operator instructions with
			events in OpenNMS. If this information is available, it 
			will be stored here."
	::= { events 20 }

ifresolve		OBJECT-TYPE
	SYNTAX		DisplayString
	MAX-ACCESS		read-only
	STATUS		current
	DESCRIPTION 	"An attempt will be made to resolve the FQDN of
			the IP address in OpenNMS-event-interface and
			if successful, the value returned will be stored here."
	::= { events 21 }

nodelabel		OBJECT-TYPE
	SYNTAX		DisplayString
	MAX-ACCESS		read-only
	STATUS		current
	DESCRIPTION 	"This will contain the name of the node as known by OpenNMS. 
			This is based solely on OpenNMS-event-nodeid and can be
			considered an authoritative way to identify the device from
			the perspective of OpenNMS.

			This name is automatically assigned in the following order:

			1) DNS Name: The reverse-resolved name of the primary
			interface for the node.

			2) NetBIOS Name: If available on a Windows or SMB system.

			3) SNMP sysName: If SNMP is available, the sysName.

			4) IP Address

			All of these methods can be overridden by an end user via the webUI, 
			and thus the value can change over time, although the 
			OpenNMS-event-nodeid will not."
	::= { events 22 }

tl1amRawMessage	OBJECT-TYPE
	SYNTAX		DisplayString
	MAX-ACCESS		read-only
	STATUS		current
	DESCRIPTION
				"The raw TL1 autonomous message in its entirety."
	::= { tl1AutonomousMessage 1 }
	
tl1amAlarmCode	OBJECT-TYPE
	SYNTAX		DisplayString
	MAX-ACCESS		read-only
	STATUS		current
	DESCRIPTION
				"The ASCII alarm-code for this TL1 autonomous message."
	::= { tl1AutonomousMessage 2 }

tl1amAutonomousTag	OBJECT-TYPE
	SYNTAX			DisplayString
	MAX-ACCESS			read-only
	STATUS			current
	DESCRIPTION
				"The ASCII autonomous-tag for this TL1 autonomous message."
	::= { tl1AutonomousMessage 3 }

tl1amVerb		OBJECT-TYPE
	SYNTAX		DisplayString
	MAX-ACCESS		read-only
	STATUS		current
	DESCRIPTION
				"The ASCII verb for this TL1 autonomous message.
				Should always be REPT."
	::= { tl1AutonomousMessage 4 }

tl1amAutoBlock	OBJECT-TYPE
	SYNTAX		DisplayString
	MAX-ACCESS		read-only
	STATUS		current
	DESCRIPTION
				"The ASCII auto-block for this TL1 autonomous message."
	::= { tl1AutonomousMessage 5 }

tl1amAID		OBJECT-TYPE
	SYNTAX		DisplayString
	MAX-ACCESS		read-only
	STATUS		current
	DESCRIPTION
				"The ASCII AID (MAX-ACCESS identifier) for this TL1 autonomous
				message, as parsed from the auto-block."
	::= { tl1AutonomousMessage 6 }

tl1amAdditionalParams	OBJECT-TYPE
	SYNTAX				DisplayString
	MAX-ACCESS				read-only
	STATUS				current
	DESCRIPTION
						"The additional parameters for this TL1 autonomous message,
						as parsed from the auto-block."
	::= { tl1AutonomousMessage 7 }
				   
alarmId		OBJECT-TYPE
	SYNTAX		DisplayString
	MAX-ACCESS		read-only
	STATUS		current
	DESCRIPTION 	"The unique alarm identifier."
	::= { eventsAlarms 1 } 
 
synchronizing		OBJECT-TYPE
	SYNTAX		DisplayString
	MAX-ACCESS		read-only
	STATUS		current
	DESCRIPTION 	"flag indicating if the alarm is due to 
                         a synchronization session (SYNC) or not (null)"
	::= { eventsAlarms 2 }
					   							   
eventTrap	NOTIFICATION-TYPE
	OBJECTS {
		dbid,
		distPoller,
		create-time,
		master-station,
		uei,
		source,
		nodeid,
		time,
		host,
		interface,
		snmphost,
		service,
		descr,
		logmsg,
		severity,
		pathoutage,
		operinst,
		ifresolve,
		nodelabel
		}
	STATUS	current
	DESCRIPTION 
	"This is the definition of the generic OpenNMS trap sent from the
	scriptd process. Key variables are uei (which tells what type
	of OpenNMS event this was), interface (the IP address of the interface
	that caused the event) and severity."
	::=  {  traps  1  }

tl1AutonomousMessageTrap	NOTIFICATION-TYPE	
	OBJECTS {
		nodeid,
		time,
		host,
		interface,
		service,
		severity,
		tl1amRawMessage,
		tl1amAlarmCode,
		tl1amAutonomousTag,
		tl1amVerb,
		tl1amAutoBlock,
		tl1amAID,
		tl1amAdditionalParams
	}
	STATUS			current
	DESCRIPTION
		"This trap is used to convey the contents of a TL1 autonomous message
		received from a TL1 NE or a north-bound TL1 EMS. Managers receiving
		this trap may need to perform additional analysis of its varbinds in
		order to realize value from this trap."
	::=  {  traps  2  }

alarmTrap	NOTIFICATION-TYPE
	OBJECTS		{ 		
		dbid,
		distPoller,
		create-time,
		master-station,
		uei,
		source,
		nodeid,
		time,
		host,
		interface,
		snmphost,
		service,
		descr,
		logmsg,
		severity,
		pathoutage,
		operinst,
		ifresolve,
		nodelabel,
		alarmId,
		synchronizing 
		}
	STATUS			current
	DESCRIPTION		
		"The OpenNMS alarm SNMP Trap"
		
	::=  {  traps 3  }

heartbeatTrap	NOTIFICATION-TYPE   
	STATUS			current
	DESCRIPTION
		"Trap sent periodically by OpenNMS to keep alive external SNMP Manager"
	::=  {  traps  4  }
             
startSyncTrap	NOTIFICATION-TYPE      
	STATUS			current
	DESCRIPTION
		"OpenNMS Synchronization Process is starting"
	::=  {  traps  5  }
                                           
endSyncTrap	NOTIFICATION-TYPE      
	STATUS			current
	DESCRIPTION
		"OpenNMS Synchronization Process is successfully ended"
	::=  {  traps  6  }
                                           
syncRequestTrap NOTIFICATION-TYPE  
	STATUS			current
  	DESCRIPTION 
    	"OpenNMS synchronization request" 
	::=  {  traps  7  }       

events-Group	OBJECT-GROUP
	OBJECTS {
		dbid,
		distPoller,
		create-time,
		master-station,
		uei,
		source,
		nodeid,
		time,
		host,
		interface,
		snmphost,
		service,
		descr,
		logmsg,
		severity,
		pathoutage,
		operinst,
		ifresolve,
		nodelabel
	}
	STATUS current
	DESCRIPTION 
		"Conformance Group for OpenNMS Events"
	::= { groups 1 }
							
tl1AutonomousMessage-Group	OBJECT-GROUP
	OBJECTS {
		tl1amRawMessage,
		tl1amAlarmCode,
		tl1amAutonomousTag,
		tl1amVerb,
		tl1amAutoBlock,
		tl1amAID,
		tl1amAdditionalParams
	}
	STATUS current
	DESCRIPTION 
		"Conformance Group for TL1 autonomous message"
	::= { groups 2 }

eventsAlarms-Group	OBJECT-GROUP
	OBJECTS {
		alarmId,
		synchronizing
	}
	STATUS current
	DESCRIPTION 
		"Conformance Group for OpenNMS Events related to Alarms "
	::= { groups 3 }																	

traps-Group	NOTIFICATION-GROUP
	NOTIFICATIONS {
		eventTrap,
		tl1AutonomousMessageTrap,
		alarmTrap, 
		heartbeatTrap,
                startSyncTrap, 
		endSyncTrap, 
		syncRequestTrap
	}
	STATUS current
	DESCRIPTION 
		"OpenNMS Notification Group"
	::= { groups 4 }	

END
