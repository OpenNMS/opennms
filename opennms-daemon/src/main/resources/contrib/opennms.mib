--
-- OPENNMS-MIB       module definition
--

-- Copyright (C) 2005-2008 by The OpenNMS Group, Inc.


-- Version 1.0 - 2005-01-13: 	The main purpose of this first version of
--				the OpenNMS MIB is to instrument the values
--				passed in the trap sent by scriptd in the
--				example configuration file.

-- Version 1.1 - 2005-12-01: 	Added the ifresolve and nodelabel fields
--				for events. Also greatly increased the text
--				associated with each object.

-- Version 1.2 - 2008-09-16:	Drop-cased first letter of all OBJECTs
--				to placate smilint.

-- Version 1.3 - 2008-09-16:	Added TL1-specific objects and trap definition

OPENNMS-MIB DEFINITIONS ::= BEGIN
IMPORTS
   OBJECT-TYPE FROM RFC-1212
   DisplayString FROM RFC1213-MIB
   enterprises FROM RFC1155-SMI
   TRAP-TYPE FROM RFC-1215
   TimeTicks FROM RFC1155-SMI
   IpAddress FROM RFC1155-SMI;

openNMS				OBJECT IDENTIFIER
							::= { enterprises 5813 }

openNMS-traps			OBJECT IDENTIFIER
							::= { openNMS 1 }

openNMS-data			OBJECT IDENTIFIER
							::= { openNMS 20 }

openNMS-events			OBJECT IDENTIFIER
							::= { openNMS-data 1 }

openNMS-eventsSpecific	OBJECT IDENTIFIER
							::= { openNMS-data 2 }
							
tl1AutonomousMessage	OBJECT IDENTIFIER
							::= { openNMS-eventsSpecific 1 }

openNMS-event-dbid		OBJECT-TYPE
	SYNTAX		DisplayString
	ACCESS		read-only
	STATUS		mandatory
	DESCRIPTION 	"This is the database ID for the event. Each
			event in OpenNMS is assigned a unique, sequential
			eventid. Unless the database is cleared, the 
			sequence should never repeat."
	::= { openNMS-events 1 }

openNMS-event-distPoller	OBJECT-TYPE
	SYNTAX		DisplayString
	ACCESS		read-only
	STATUS		mandatory
	DESCRIPTION 	"This is the distributed poller name for the event."
	::= { openNMS-events 2 }

openNMS-event-create-time	OBJECT-TYPE
	SYNTAX		DisplayString
	ACCESS		read-only
	STATUS		mandatory
	DESCRIPTION 	"This is the time the event was created in the database."
	::= { openNMS-events 3 }

openNMS-event-master-station	OBJECT-TYPE
	SYNTAX		DisplayString
	ACCESS		read-only
	STATUS		mandatory
	DESCRIPTION 	"This is the name of the master station for the event."
	::= { openNMS-events 4 }

openNMS-event-uei		OBJECT-TYPE
	SYNTAX		DisplayString
	ACCESS		read-only
	STATUS		mandatory
	DESCRIPTION 	"This is the Unique Event Identifier (UEI) for the event.
			 The UEI is a string that should be descriptive and unique
			 for each event type that OpenNMS handles."
	::= { openNMS-events 6 }

openNMS-event-source		OBJECT-TYPE
	SYNTAX		DisplayString
	ACCESS		read-only
	STATUS		mandatory
	DESCRIPTION 	"This is the source of the event, usually the OpenNMS process
			name, such as Capsd or Trapd."
	::= { openNMS-events 7 }

openNMS-event-nodeid		OBJECT-TYPE
	SYNTAX		DisplayString
	ACCESS		read-only
	STATUS		mandatory
	DESCRIPTION 	"This is the Node ID for the event. Node IDs are simply
			a handle that OpenNMS uses to group interfaces and services
			together, and each node should represent an actual device."
	::= { openNMS-events 8 }

openNMS-event-time		OBJECT-TYPE
	SYNTAX		DisplayString
	ACCESS		read-only
	STATUS		mandatory
	DESCRIPTION 	"This is the time the event occurred."
	::= { openNMS-events 9 }

openNMS-event-host		OBJECT-TYPE
	SYNTAX		DisplayString
	ACCESS		read-only
	STATUS		mandatory
	DESCRIPTION 	"This is the host for the event. In most cases it will
			represent the OpenNMS instance that generated it."
	::= { openNMS-events 10 }

openNMS-event-interface		OBJECT-TYPE
	SYNTAX		DisplayString
	ACCESS		read-only
	STATUS		mandatory
	DESCRIPTION 	"This is the interface for the event. It should contain
			the IP address of the interface that caused the event."
	::= { openNMS-events 11 }

openNMS-event-snmphost		OBJECT-TYPE
	SYNTAX		DisplayString
	ACCESS		read-only
	STATUS		mandatory
	DESCRIPTION 	"This is the SNMP host for the event. In the case of
			an SNMP Trap that was received by OpenNMS, it will 
			reflect the device that generated the trap. In the
			case of a trap generated by OpenNMS, such as forwarding
			a nodeLostService event to another system, it will
			reflect the OpenNMS server."
	::= { openNMS-events 12 }

openNMS-event-service		OBJECT-TYPE
	SYNTAX		DisplayString
	ACCESS		read-only
	STATUS		mandatory
	DESCRIPTION 	"This is the name of the service (ICMP, SSH, HTTP, etc.)
			that is associated with the event. For example, a failed 
			web server may generate a nodeLostService event. In that
			case this field would most likely read HTTP."
	::= { openNMS-events 13 }

openNMS-event-descr		OBJECT-TYPE
	SYNTAX		DisplayString
	ACCESS		read-only
	STATUS		mandatory
	DESCRIPTION 	"This is the verbose description of the event."
	::= { openNMS-events 16 }

openNMS-event-logmsg		OBJECT-TYPE
	SYNTAX		DisplayString
	ACCESS		read-only
	STATUS		mandatory
	DESCRIPTION 	"The log message is a short, usually one sentence, description of
			the event suitable for displaying in a log or table."
	::= { openNMS-events 17 }

openNMS-event-severity		OBJECT-TYPE
	SYNTAX		DisplayString
	ACCESS		read-only
	STATUS		mandatory
	DESCRIPTION 	"This is the severity of the event, one of CLEARED,
			INDETERMINATE, NORMAL, WARNING, MINOR, MAJOR or CRITICAL."
	::= { openNMS-events 18 }

openNMS-event-pathoutage	OBJECT-TYPE
	SYNTAX		DisplayString
	ACCESS		read-only
	STATUS		optional
	DESCRIPTION 	"The pathoutage field in the event has yet to be implemented,
			but it will be stored here when available."
	::= { openNMS-events 19 }

openNMS-event-operinst		OBJECT-TYPE
	SYNTAX		DisplayString
	ACCESS		read-only
	STATUS		mandatory
	DESCRIPTION 	"It is possible to associate operator instructions with
			events in OpenNMS. If this information is available, it 
			will be stored here."
	::= { openNMS-events 20 }

openNMS-event-ifresolve		OBJECT-TYPE
	SYNTAX		DisplayString
	ACCESS		read-only
	STATUS		mandatory
	DESCRIPTION 	"An attempt will be made to resolve the FQDN of
			the IP address in OpenNMS-event-interface and
			if successful, the value returned will be stored here."
	::= { openNMS-events 21 }

openNMS-event-nodelabel		OBJECT-TYPE
	SYNTAX		DisplayString
	ACCESS		read-only
	STATUS		mandatory
	DESCRIPTION 	"This will contain the name of the node as known by OpenNMS. 
			This is based solely on OpenNMS-event-nodeid and can be
			considered an authoritative way to identify the device from
			the perspective of OpenNMS.

			This name is automatically assigned in the following order:

			1) DNS Name: The reverse-resolved name of the primary
			interface for the node.

			2) NetBIOS Name: If available on a Windows or SMB system.

			3) SNMP sysName: If SNMP is available, the sysName.

			4) IP Address

			All of these methods can be overridden by an end user via the webUI, 
			and thus the value can change over time, although the 
			OpenNMS-event-nodeid will not."
	::= { openNMS-events 22 }

tl1amRawMessage	OBJECT-TYPE
	SYNTAX		DisplayString
	ACCESS		read-only
	STATUS		mandatory
	DESCRIPTION
				"The raw TL1 autonomous message in its entirety."
	::= { tl1AutonomousMessage 1 }
	
tl1amAlarmCode	OBJECT-TYPE
	SYNTAX		DisplayString
	ACCESS		read-only
	STATUS		mandatory
	DESCRIPTION
				"The ASCII alarm-code for this TL1 autonomous message."
	::= { tl1AutonomousMessage 2 }

tl1amAutonomousTag	OBJECT-TYPE
	SYNTAX			Unsigned32
	ACCESS			read-only
	STATUS			mandatory
	DESCRIPTION
				"The numeric autonomous-tag for this TL1 autonomous message."
	::= { tl1AutonomousMessage 3 }

tl1amVerb		OBJECT-TYPE
	SYNTAX		DisplayString
	ACCESS		read-only
	STATUS		mandatory
	DESCRIPTION
				"The ASCII verb for this TL1 autonomous message.
				Should always be REPT."
	::= { tl1AutonomousMessage 4 }

tl1amAutoBlock	OBJECT-TYPE
	SYNTAX		DisplayString
	ACCESS		read-only
	STATUS		mandatory
	DESCRIPTION
				"The ASCII auto-block for this TL1 autonomous message."
	::= { tl1AutonomousMessage 5 }

tl1amAID		OBJECT-TYPE
	SYNTAX		DisplayString
	ACCESS		read-only
	STATUS		mandatory
	DESCRIPTION
				"The ASCII AID (access identifier) for this TL1 autonomous
				message, as parsed from the auto-block."
	::= { tl1AutonomousMessage 6 }

tl1amAdditionalParams	OBJECT-TYPE
	SYNTAX				DisplayString
	ACCESS				read-only
	STATUS				mandatory
	DESCRIPTION
						"The additional parameters for this TL1 autonomous message,
						as parsed from the auto-block."
	::= { tl1AutonomousMessage 7 }
				
-- Trap definitions

openNMS-Generic-Trap		TRAP-TYPE
	ENTERPRISE openNMS-traps
	VARIABLES {
		openNMS-event-dbid,
		openNMS-event-distPoller,
		openNMS-event-create-time,
		openNMS-event-master-station,
		openNMS-event-uei,
		openNMS-event-source,
		openNMS-event-nodeid,
		openNMS-event-time,
		openNMS-event-host,
		openNMS-event-interface,
		openNMS-event-snmphost,
		openNMS-event-service,
		openNMS-event-descr,
		openNMS-event-logmsg,
		openNMS-event-severity,
		openNMS-event-pathoutage,
		openNMS-event-operinst,
		openNMS-event-ifresolve,
		openNMS-event-nodelabel
		}
	DESCRIPTION 
	"This is the definition of the generic OpenNMS trap sent from the
        scriptd process. Key variables are uei (which tells what type
        of OpenNMS event this was), interface (the IP address of the interface
	that caused the event) and severity."
	::= 1

openNMS-tl1AutonomousMessageTrap	TRAP-TYPE
	ENTERPRISE openNMS-traps
	VARIABLES {
		openNMS-event-nodeid,
		openNMS-event-time,
		openNMS-event-host,
		openNMS-event-interface,
		openNMS-event-service,
		openNMS-event-severity,
		tl1amRawMessage,
		tl1amAlarmCode,
		tl1amAutonomousTag,
		tl1amVerb,
		tl1amAutoBlock,
		tl1amAID,
		tl1amAdditionalParams
	}
	DESCRIPTION
		"This trap is used to convey the contents of a TL1 autonomous message
		received from a TL1 NE or a north-bound TL1 EMS. Managers receiving
		this trap may need to perform additional analysis of its varbinds in
		order to realize value from this trap."
	::= 2

END
