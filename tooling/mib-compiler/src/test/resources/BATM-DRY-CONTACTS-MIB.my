BATM-DRY-CONTACTS-MIB DEFINITIONS ::= BEGIN

IMPORTS
     MODULE-IDENTITY, OBJECT-TYPE, TimeTicks
        FROM SNMPv2-SMI

     RowPointer
        FROM SNMPv2-TC

     switch
        FROM BATM-SWITCH-MIB; 
          
batmDryContactsMIB MODULE-IDENTITY
        LAST-UPDATED "200711270000Z"
        ORGANIZATION "BATM Advanced Communication"
        CONTACT-INFO   

        "BATM/Telco Systems Support team
				Email: 
				For North America: techsupport@telco.com
				For North Europe: support@batm.de, info@batm.de
				For the rest of the world: techsupport@telco.com"

        DESCRIPTION
        "Initial version. This MIB provides external-alarm management and notifications"
        
         -- revision history         
        REVISION     "200711270000Z"
         DESCRIPTION
         "Compilation fixes"
         
       ::= { switch 112 }
-- Textual Conventions

-- tables

dryContactsObjects OBJECT IDENTIFIER ::= { batmDryContactsMIB 1 }

--traps
dryContactsNotifications OBJECT IDENTIFIER ::= { batmDryContactsMIB 2 }
inputStateChangedNotification OBJECT IDENTIFIER ::= { dryContactsNotifications 1 }

inputsCfgTable  OBJECT-TYPE
	SYNTAX SEQUENCE OF InputsCfgEntry
	MAX-ACCESS not-accessible
	STATUS current
	DESCRIPTION
	"A table containing inputs configuration and statuses"
	::= { dryContactsObjects 1 }

inputsCfgEntry OBJECT-TYPE
	SYNTAX InputsCfgEntry
	MAX-ACCESS not-accessible
	STATUS current
	DESCRIPTION
		""
	INDEX  { extAlarmID }
	::= { inputsCfgTable 1 }

InputsCfgEntry ::= SEQUENCE {
	extAlarmID INTEGER,
	name	OCTET STRING,
	description OCTET STRING,
	enableStatus INTEGER,
	alarmStatus INTEGER,
	alarmSeverity INTEGER,
	polarity INTEGER,
	lastChange TimeTicks
	}

extAlarmID OBJECT-TYPE
SYNTAX INTEGER
MAX-ACCESS read-only
STATUS current
DESCRIPTION
		"External alarm index uniquely identifies this row. 
		An integer with supported range of values 1-4. Index. Not-accessible"
        ::= { inputsCfgEntry 1}

name OBJECT-TYPE
SYNTAX OCTET STRING
MAX-ACCESS read-write
STATUS current
DESCRIPTION
	"Name of alarm. An OCTET-STRING with max. 16 OCTETS. 
	Default value null string. Read-write"
	::= { inputsCfgEntry 2}

description OBJECT-TYPE
SYNTAX OCTET STRING
MAX-ACCESS read-write
STATUS current
DESCRIPTION
	"Alarm description. An OCTET-STRING with max. 64 OCTETS. 
	Default value null string. Read-write"
	::= { inputsCfgEntry 3}


enableStatus OBJECT-TYPE
SYNTAX INTEGER {
        enabled(1),
        disabled(2)
}
MAX-ACCESS read-write
STATUS current
DESCRIPTION
	"Senging alarms status. An enumeration with two values: enabled(1), disabled(2). 
	Default value is disabled(2). Read-write"
	::= { inputsCfgEntry 4}


alarmStatus OBJECT-TYPE
SYNTAX INTEGER {
	no-alarm(1),
	alarm(2)
}
MAX-ACCESS read-only
STATUS current
DESCRIPTION
	"Alarm status. An enumeration with two values: no-alarm(1), alarm(2). 
	Default value is no-alarm(1). Read-only."
	::= { inputsCfgEntry 5 }

alarmSeverity OBJECT-TYPE
SYNTAX INTEGER {
	info(1),
	minor(2),
	major(3),
	critical(4)
}
MAX-ACCESS read-write
STATUS current
DESCRIPTION
	"Configured alarm severity. An enumeration with 4 values: 
	info(1), minor(2), major(3) and critical(4). 
	Default value is info(1). Read-write"
	::= { inputsCfgEntry 6}

polarity OBJECT-TYPE
SYNTAX INTEGER {
	normally-opened(1),
	normally-closed(2)
}
MAX-ACCESS read-write
STATUS current
DESCRIPTION
	"Configured polarity. 
	An enumeration with 2 values: normally-opened(1), normally-closed(2). 
	Default value is normally-opened(1). Read-write"
	::= { inputsCfgEntry 7}

lastChange  OBJECT-TYPE
SYNTAX TimeTicks
MAX-ACCESS read-only
STATUS current
DESCRIPTION
	"The value of sysUpTime at the time of the last operational status change. 
	TimeTicks. Read-only"
	::= { inputsCfgEntry 8}


-- Notifications.

inputStateChanged NOTIFICATION-TYPE
OBJECTS {
	extAlarmID ,
	name,
	description,
	alarmStatus,
	alarmSeverity
}
STATUS current
   DESCRIPTION
        "Send notification when operational status of the input changes"
   ::= { inputStateChangedNotification 1 }

END
