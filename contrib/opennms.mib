--
-- OPENNMS-MIB       module definition
--

-- Copyright (C) 2005 by The OpenNMS Group, Inc.


-- Version 1.0 - 2005-01-13: 	The main purpose of this first version of
--				the OpenNMS MIB is to instrument the values
--				passed in the trap sent by scriptd in the
--				example configuration file.

-- Version 1.1 - 2005-12-01: 	Added the ifresolve and nodelabel fields
--				for events. Also greatly increased the text
--				associated with each object.

OPENNMS-MIB DEFINITIONS ::= BEGIN
IMPORTS
   OBJECT-TYPE FROM RFC-1212
   DisplayString FROM RFC1213-MIB
   enterprises FROM RFC1155-SMI
   TRAP-TYPE FROM RFC-1215
   TimeTicks FROM RFC1155-SMI
   IpAddress FROM RFC1155-SMI;

OpenNMS				OBJECT IDENTIFIER
							::= { enterprises 5813 }

OpenNMS-traps			OBJECT IDENTIFIER
							::= { OpenNMS 1 }

OpenNMS-data			OBJECT IDENTIFIER
							::= { OpenNMS 20 }

OpenNMS-events			OBJECT IDENTIFIER
							::= { OpenNMS-data 1 }

OpenNMS-event-dbid		OBJECT-TYPE
	SYNTAX		DisplayString
	ACCESS		read-only
	STATUS		mandatory
	DESCRIPTION 	"This is the database ID for the event. Each
			event in OpenNMS is assigned a unique, sequential
			eventid. Unless the database is cleared, the 
			sequence should never repeat."
	::= { OpenNMS-events 1 }

OpenNMS-event-distPoller	OBJECT-TYPE
	SYNTAX		DisplayString
	ACCESS		read-only
	STATUS		mandatory
	DESCRIPTION 	"This is the distributed poller name for the event."
	::= { OpenNMS-events 2 }

OpenNMS-event-create-time	OBJECT-TYPE
	SYNTAX		DisplayString
	ACCESS		read-only
	STATUS		mandatory
	DESCRIPTION 	"This is the time the event was created in the database."
	::= { OpenNMS-events 3 }

OpenNMS-event-master-station	OBJECT-TYPE
	SYNTAX		DisplayString
	ACCESS		read-only
	STATUS		mandatory
	DESCRIPTION 	"This is the name of the master station for the event."
	::= { OpenNMS-events 4 }

OpenNMS-event-uei		OBJECT-TYPE
	SYNTAX		DisplayString
	ACCESS		read-only
	STATUS		mandatory
	DESCRIPTION 	"This is the Unique Event Identifier (UEI) for the event.
			 The UEI is a string that should be descriptive and unique
			 for each event type that OpenNMS handles."
	::= { OpenNMS-events 6 }

OpenNMS-event-source		OBJECT-TYPE
	SYNTAX		DisplayString
	ACCESS		read-only
	STATUS		mandatory
	DESCRIPTION 	"This is the source of the event, usually the OpenNMS process
			name, such as Capsd or Trapd."
	::= { OpenNMS-events 7 }

OpenNMS-event-nodeid		OBJECT-TYPE
	SYNTAX		DisplayString
	ACCESS		read-only
	STATUS		mandatory
	DESCRIPTION 	"This is the Node ID for the event. Node IDs are simply
			a handle that OpenNMS uses to group interfaces and services
			together, and each node should represent an actual device."
	::= { OpenNMS-events 8 }

OpenNMS-event-time		OBJECT-TYPE
	SYNTAX		DisplayString
	ACCESS		read-only
	STATUS		mandatory
	DESCRIPTION 	"This is the time the event occurred."
	::= { OpenNMS-events 9 }

OpenNMS-event-host		OBJECT-TYPE
	SYNTAX		DisplayString
	ACCESS		read-only
	STATUS		mandatory
	DESCRIPTION 	"This is the host for the event. In most cases it will
			represent the OpenNMS instance that generated it."
	::= { OpenNMS-events 10 }

OpenNMS-event-interface		OBJECT-TYPE
	SYNTAX		DisplayString
	ACCESS		read-only
	STATUS		mandatory
	DESCRIPTION 	"This is the interface for the event. It should contain
			the IP address of the interface that caused the event."
	::= { OpenNMS-events 11 }

OpenNMS-event-snmphost		OBJECT-TYPE
	SYNTAX		DisplayString
	ACCESS		read-only
	STATUS		mandatory
	DESCRIPTION 	"This is the SNMP host for the event. In the case of
			an SNMP Trap that was received by OpenNMS, it will 
			reflect the device that generated the trap. In the
			case of a trap generated by OpenNMS, such as forwarding
			a nodeLostService event to another system, it will
			reflect the OpenNMS server."
	::= { OpenNMS-events 12 }

OpenNMS-event-service		OBJECT-TYPE
	SYNTAX		DisplayString
	ACCESS		read-only
	STATUS		mandatory
	DESCRIPTION 	"This is the name of the service (ICMP, SSH, HTTP, etc.)
			that is associated with the event. For example, a failed 
			web server may generate a nodeLostService event. In that
			case this field would most likely read HTTP."
	::= { OpenNMS-events 13 }

OpenNMS-event-descr		OBJECT-TYPE
	SYNTAX		DisplayString
	ACCESS		read-only
	STATUS		mandatory
	DESCRIPTION 	"This is the verbose description of the event."
	::= { OpenNMS-events 16 }

OpenNMS-event-logmsg		OBJECT-TYPE
	SYNTAX		DisplayString
	ACCESS		read-only
	STATUS		mandatory
	DESCRIPTION 	"The log message is a short, usually one sentence, description of
			the event suitable for displaying in a log or table."
	::= { OpenNMS-events 17 }

OpenNMS-event-severity		OBJECT-TYPE
	SYNTAX		DisplayString
	ACCESS		read-only
	STATUS		mandatory
	DESCRIPTION 	"This is the severity of the event, one of CLEARED,
			INDETERMINATE, NORMAL, WARNING, MINOR, MAJOR or CRITICAL."
	::= { OpenNMS-events 18 }

OpenNMS-event-pathoutage	OBJECT-TYPE
	SYNTAX		DisplayString
	ACCESS		read-only
	STATUS		optional
	DESCRIPTION 	"The pathoutage field in the event has yet to be implemented,
			but it will be stored here when available."
	::= { OpenNMS-events 19 }

OpenNMS-event-operinst		OBJECT-TYPE
	SYNTAX		DisplayString
	ACCESS		read-only
	STATUS		mandatory
	DESCRIPTION 	"It is possible to associate operator instructions with
			events in OpenNMS. If this information is available, it 
			will be stored here."
	::= { OpenNMS-events 20 }

OpenNMS-event-ifresolve		OBJECT-TYPE
	SYNTAX		DisplayString
	ACCESS		read-only
	STATUS		mandatory
	DESCRIPTION 	"An attempt will be made to resolve the FQDN of
			the IP address in OpenNMS-event-interface and
			if successful, the value returned will be stored here."
	::= { OpenNMS-events 21 }

OpenNMS-event-nodelabel		OBJECT-TYPE
	SYNTAX		DisplayString
	ACCESS		read-only
	STATUS		mandatory
	DESCRIPTION 	"This will contain the name of the node as known by OpenNMS. 
			This is based solely on OpenNMS-event-nodeid and can be
			considered an authoritative way to identify the device from
			the perspective of OpenNMS.

			This name is automatically assigned in the following order:

			1) DNS Name: The reverse-resolved name of the primary
			interface for the node.

			2) NetBIOS Name: If available on a Windows or SMB system.

			3) SNMP sysName: If SNMP is available, the sysName.

			4) IP Address

			All of these methods can be overridden by an end user via the webUI, 
			and thus the value can change over time, although the 
			OpenNMS-event-nodeid will not."
	::= { OpenNMS-events 22 }

OpenNMS-Generic-Trap		TRAP-TYPE
	ENTERPRISE OpenNMS-traps
	VARIABLES {
		OpenNMS-event-dbid,
		OpenNMS-event-distPoller,
		OpenNMS-event-create-time,
		OpenNMS-event-master-station,
		OpenNMS-event-uei,
		OpenNMS-event-source,
		OpenNMS-event-nodeid,
		OpenNMS-event-time,
		OpenNMS-event-host,
		OpenNMS-event-interface,
		OpenNMS-event-snmphost,
		OpenNMS-event-service,
		OpenNMS-event-descr,
		OpenNMS-event-logmsg,
		OpenNMS-event-severity,
		OpenNMS-event-pathoutage,
		OpenNMS-event-operinst,
		OpenNMS-event-ifresolve,
		OpenNMS-event-nodelabel
		}
	DESCRIPTION 
	"This is the definition of the generic OpenNMS trap sent from the
        scriptd process. Key variables are uei (which tells what type
        of OpenNMS event this was), interface (the IP address of the interface
	that caused the event) and severity."
	::= 1

END
